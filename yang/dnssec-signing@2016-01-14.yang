module dnssec-signing {

  yang-version "1.1";

  namespace "http://www.nic.cz/ns/yang/dnssec-signing";

  prefix "dnssec";

  import ietf-yang-types {
    prefix "yang";
  }

  import dns-server {
    prefix "dnss";
  }

  import dnssec-algorithms {
    prefix "dsalg";
  }

  organization
    "CZ.NIC, z. s. p. o.";

  contact
    "Editor:   Ladislav Lhotka
               <mailto:lhotka@nic.cz>";

  description
    "This YANG module defines configuration data and RPC operations
     for automatic DNSSEC signatures.";

  revision 2016-01-14 {
    description
      "Initial revision.";
    reference
      "TODO: put git tag here";
  }

  /* Typedefs */

  typedef lifetime {
    type uint32;
    units "seconds";
    description
      "This type is used for the lifetime values of keys and
       signatures.";
  }

  typedef key-id {
    type string {
      length "40";
    }
    description
      "This type is used for identifiers of DNSSEC keys.";
  }

  /* Groupings */

  grouping zone-options {
    description
      "Zone options that configure DNSSEC signing.";
    container dnssec-signing {
      presence "automatic DNSSEC signing";
      description
        "Configuration of automatic DNSSEC signing.";
      leaf enabled {
        type boolean;
        default "true";
        description
          "This flag allows to disable automatic DNSSEC signing while
           keeping its configuration in place.";
      }
      leaf policy {
        type leafref {
          path "/dnss:dns-server/dnssec:sign-policy/dnssec:name";
        }
        description
          "Reference to a signing policy.

           If this leaf is present, ZSKs are generated automatically
           according to the signing policy.";
      }
    }
  }

  grouping key-parameters {
    description
      "Common parameters of DNSSEC keys.";
    leaf algorithm {
      type dsalg:dnssec-algorithm;
      mandatory "true";
      description
        "Encryption algorithm for which the key works.";
    }
    leaf length {
      type uint16;
      units "bits";
      mandatory "true";
      description
        "Length of the key.";
    }
    leaf publish {
      type yang:date-and-time;
      description
        "The time of key publication (the key appears as a DNSKEY
         resource record in the zone).

         Absence of this leaf means the key is published immediately
         after the key is created.";
    }
    leaf activate {
      type yang:date-and-time;
      description
        "Start of the time interval in which the key is used for
         signing.

         Absence of this leaf means the key is used for signing since
         the time of publishing.";
    }
    leaf retire {
      type yang:date-and-time;
      description
        "End of the time interval in which the key is used for
         signing.

         Absence of this leaf means the key is never retired.";
    }
    leaf remove {
      type yang:date-and-time;
      description
        "The time of DNSKEY RR removal.

         Absence of this leaf means the key is never removed.";
    }
  }

  /* State data */

  augment "/dnss:dns-server-state/dnss:zone" {
    description
      "State data for zone DNSSEC signing.";
    container dnssec-signing {
      description
        "State data related to automatic DNSSEC signing.";
      leaf enabled {
        type boolean;
        description
          "Is DNSSEC signing is enabled for the ancestor zone?";
      }
      list key {
        key "key-id";
        description
          "Parameters of a DNSSEC key.";
        leaf key-id {
          type key-id;
          description
            "Key identifier.";
        }
        leaf key-tag {
          type uint16;
          mandatory "true";
          description
            "Key tag.";
          reference
            "RFC 4034: Resource Records for the DNS Security
             Extensions.";
        }
        uses key-parameters;
        leaf created {
          type yang:date-and-time;
          description
            "Date and time when the key was created.";
        }
        leaf flags {
          type bits {
            bit zone-key {
              position "7";
              description
                "This flag indicates a DNS zone key.";
            }
            bit secure-entry-point {
              position "15";
              description
                "This flag indicates a key intended for use as a
                 secure entry point, i.e., key-signing key.";
            }
          }
          description
            "Key flags.";
          reference
            "RFC 4034: Resource Records for the DNS Security
             Extensions.";
        }
      }
    }
  }

  /* Configuration data */

  augment "/dnss:dns-server" {
    description
      "Augment DNS server configuration with a list of DNSSEC signing
       policies.";
    list sign-policy {
      key "name";
      description
        "A named DNSSEC signing policy.";
      uses dnss:entry-name;
      leaf algorithm {
        type dsalg:dnssec-algorithm;
        default "RSASHA256";
        description
          "Algorithm used for signing keys and issued signatures.";
      }
      leaf ksk-length {
        type uint16;
        units "bits";
        default "2048";
        description
          "Length of generated key-signing keys.";
      }
      leaf zsk-length {
        type uint16;
        units "bits";
        default "1024";
        description
          "Length of generated zone-signing keys.";
      }
      leaf dnskey-ttl {
        type dnss:rr-ttl;
        description
          "TTL value for DNSKEY records added to zone apex.";
      }
      leaf zsk-lifetime {
        type lifetime;
        default "2592000";
        description
          "Time interval after which ZSK rollover will be initiated.

           The default value corresponds to 30 days.";
      }
      leaf rrsig-lifetime {
        type lifetime;
        default "1209600";
        description
          "Lifetime of newly issued signatures.

           The default value corresponds to two weeks.";
      }
      leaf rrsig-refresh {
        type uint32;
        units "seconds";
        default "604800";
        description
          "This parameter specifies how long before signature
           expiration the signature will be refreshed.

           The default value corresponds to one week.";
      }
      leaf nsec3 {
        type boolean;
        default "false";
        description
          "This flag specifies whether NSEC3 will be used instead of
           NSEC.";
      }
      leaf soa-min-ttl {
        type dnss:rr-ttl;
        description
          "SOA minimum TTL value.";
      }
      leaf zone-max-ttl {
        type dnss:rr-ttl;
        description
          "Maximum TTL value present in the zone.";
      }
      leaf propagation-delay {
        type uint32;
        units "seconds";
        default "3600";
        description
          "Extra delay added to every key rollover step.";
      }
    }
  }

  augment "/dnss:dns-server/dnss:zones/dnss:template" {
    description
      "DNSSEC signing configuration for a zone template.";
    uses dnssec:zone-options;
  }

  augment "/dnss:dns-server/dnss:zones/dnss:zone" {
    description
      "DNSSEC signing configuration for a zone.";
    uses dnssec:zone-options;
  }

  /* RPC operations */

  rpc generate-key {
    description
      "Generate a DNSSEC signing key.";
    input {
      uses key-parameters;
      leaf secure-entry-point {
        type boolean;
        default "false";
        description
          "This flag indicates that the key is the secure entry point
           of the corresponding zone, i.e., a key-signing key.";
      }
    }
    output {
      leaf key-id {
        type key-id;
        mandatory "true";
        description
          "Identifier of the generated key.";
      }
      leaf key-tag {
        type uint16;
        mandatory "true";
        description
          "Tag of the generated key.";
      }
    }
  }

  rpc zone-sign {
    description
      "Sign specified zones with available DNSSEC keys.";
    input {
      leaf-list zones {
        type dnss:zone-ref;
        description
          "Domain names of the zones to be signed.";
      }
    }
  }
}
